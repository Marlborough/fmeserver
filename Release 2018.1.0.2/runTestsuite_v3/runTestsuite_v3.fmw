FME workspace runTestsuite_v3.fmw

Creator
    GEOMTYPE = Geometry Object
    NUM = 1
    CREATED -> SystemCaller
    CREATED -> SystemCaller_2
    CREATED -> SystemCaller_4
SystemCaller_4
    CMD = "C:\squish\squish_qt\bin\squishrunner.exe --testsuite C:\squishQTForFME\suite_qtForFME --reportgen stdout,C:\squish\results_dragndrop.txt"
    -> SystemCaller_5
SystemCaller_5
    CMD = "C:\squish\squish_qt\bin\squishrunner.exe" --testsuite C:\squishQTForFME\suite_qtPublishedParam --reportgen stdout,C:\squish\results_parameters.txt
    -> SystemCaller_6
SystemCaller_6
    CMD = "C:\squish\squish_qt\bin\squishrunner.exe" --testsuite C:\squishQTForFME\suite_customTransformer --reportgen stdout,C:\squish\results_customTransformer.txt
    -> SystemCaller_4_Output
SystemCaller_4_Output: Logger
    LOG_FEATURE = LOG_ONLY
    MAXCOORDS = 20
    MAXFEATS = 20
    MESSAGE = Feature is:
    SEVERITY = INFO
SystemCaller
    CMD = start cmd.exe @cmd /k "C:\squish\squish_qt\bin\squishserver.exe"
    -> Logger_startSquishServer
Logger_startSquishServer
    MAXCOORDS = 20
    MAXFEATS = 20
    MESSAGE = Feature is:
    LOGGED -> SystemCaller_2
SystemCaller_2
    CMD = "C:\squish\squish_qt\bin\squishrunner.exe" --testsuite C:\squish\testsuite\squishQTForWeisong\squishQTProduction\suite_qtForFME --reportgen stdout,C:\squish\results_dragndrop.txt
    -> Logger_runTests
Logger_runTests
    MAXCOORDS = 20
    MAXFEATS = 20
    MESSAGE = Feature is:
    LOGGED -> Decelerator
Decelerator
    DECEL_TYPE = Per Feature Delay
    DELAY = 60
    -> SystemCaller_3
SystemCaller_3
    CMD = "c:\squish\squish_qt\bin\squishserver.exe" --stop
    -> Logger_stopSquishServer
Logger_stopSquishServer
    MAXCOORDS = 20
    MAXFEATS = 20
    MESSAGE = Feature is:
